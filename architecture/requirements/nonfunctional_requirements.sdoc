[DOCUMENT]
MID: f7a8b9c0d1e2f3a4b5c6d7e8f9a0b1c2
TITLE: Non-Functional Requirements
PREFIX: NFR-
OPTIONS:
  ENABLE_MID: True

[GRAMMAR]
IMPORT_FROM_FILE: @grammar

[TEXT]
STATEMENT: >>>
.. raw:: html

   <div style="overflow-x:auto;margin:1em 0"><svg xmlns="http://www.w3.org/2000/svg" xmlns:xlink="http://www.w3.org/1999/xlink" contentStyleType="text/css" height="228px" preserveAspectRatio="none" style="width:914px;height:228px;background:#FFFFFF;" version="1.1" viewBox="0 0 914 228" width="914px" zoomAndPan="magnify"><defs/><g><line style="stroke:#181818;stroke-width:1.5;" x1="48" x2="48" y1="65.0938" y2="85.0938"/><rect fill="#F1F1F1" height="35.0938" style="stroke:#181818;stroke-width:1.5;" width="76" x="10" y="85.0938"/><text fill="#000000" font-family="sans-serif" font-size="12" lengthAdjust="spacing" textLength="56" x="20" y="107.5508">interpreter</text><line style="stroke:#181818;stroke-width:1.5;" x1="48" x2="58" y1="143.7344" y2="143.7344"/><text fill="#000000" font-family="sans-serif" font-size="12" lengthAdjust="spacing" textLength="143" x="58" y="148.6445">INT-1  assemble text lines</text><line style="stroke:#181818;stroke-width:1.5;" x1="48" x2="58" y1="175.8281" y2="175.8281"/><text fill="#000000" font-family="sans-serif" font-size="12" lengthAdjust="spacing" textLength="107" x="58" y="180.7383">INT-2  detect format</text><line style="stroke:#181818;stroke-width:1.5;" x1="48" x2="58" y1="207.9219" y2="207.9219"/><text fill="#000000" font-family="sans-serif" font-size="12" lengthAdjust="spacing" textLength="193" x="58" y="212.832">INT-3  instantiate models + validate</text><line style="stroke:#181818;stroke-width:1.5;" x1="48" x2="48" y1="120.1875" y2="207.9219"/><line style="stroke:#181818;stroke-width:1.5;" x1="306.5" x2="306.5" y1="65.0938" y2="85.0938"/><rect fill="#F1F1F1" height="35.0938" style="stroke:#181818;stroke-width:1.5;" width="65" x="274" y="85.0938"/><text fill="#000000" font-family="sans-serif" font-size="12" lengthAdjust="spacing" textLength="45" x="284" y="107.5508">analyzer</text><line style="stroke:#181818;stroke-width:1.5;" x1="306.5" x2="316.5" y1="143.7344" y2="143.7344"/><text fill="#000000" font-family="sans-serif" font-size="12" lengthAdjust="spacing" textLength="104" x="316.5" y="148.6445">ANL-1  count cards</text><line style="stroke:#181818;stroke-width:1.5;" x1="306.5" x2="316.5" y1="175.8281" y2="175.8281"/><text fill="#000000" font-family="sans-serif" font-size="12" lengthAdjust="spacing" textLength="138" x="316.5" y="180.7383">ANL-2  determine ranges</text><line style="stroke:#181818;stroke-width:1.5;" x1="306.5" x2="316.5" y1="207.9219" y2="207.9219"/><text fill="#000000" font-family="sans-serif" font-size="12" lengthAdjust="spacing" textLength="138" x="316.5" y="212.832">ANL-3  prepare summary</text><line style="stroke:#181818;stroke-width:1.5;" x1="306.5" x2="306.5" y1="120.1875" y2="207.9219"/><line style="stroke:#181818;stroke-width:1.5;" x1="520" x2="520" y1="65.0938" y2="85.0938"/><rect fill="#F1F1F1" height="35.0938" style="stroke:#181818;stroke-width:1.5;" width="85" x="477.5" y="85.0938"/><text fill="#000000" font-family="sans-serif" font-size="12" lengthAdjust="spacing" textLength="65" x="487.5" y="107.5508">renumberer</text><line style="stroke:#181818;stroke-width:1.5;" x1="520" x2="530" y1="143.7344" y2="143.7344"/><text fill="#000000" font-family="sans-serif" font-size="12" lengthAdjust="spacing" textLength="123" x="530" y="148.6445">RNB-1  assign ranges</text><line style="stroke:#181818;stroke-width:1.5;" x1="520" x2="530" y1="175.8281" y2="175.8281"/><text fill="#000000" font-family="sans-serif" font-size="12" lengthAdjust="spacing" textLength="122" x="530" y="180.7383">RNB-2  update ID field</text><line style="stroke:#181818;stroke-width:1.5;" x1="520" x2="530" y1="207.9219" y2="207.9219"/><text fill="#000000" font-family="sans-serif" font-size="12" lengthAdjust="spacing" textLength="131" x="530" y="212.832">RNB-3  populate lookup</text><line style="stroke:#181818;stroke-width:1.5;" x1="520" x2="520" y1="120.1875" y2="207.9219"/><line style="stroke:#181818;stroke-width:1.5;" x1="716" x2="716" y1="65.0938" y2="85.0938"/><rect fill="#F1F1F1" height="35.0938" style="stroke:#181818;stroke-width:1.5;" width="64" x="684" y="85.0938"/><text fill="#000000" font-family="sans-serif" font-size="12" lengthAdjust="spacing" textLength="44" x="694" y="107.5508">exporter</text><line style="stroke:#181818;stroke-width:1.5;" x1="716" x2="726" y1="143.7344" y2="143.7344"/><text fill="#000000" font-family="sans-serif" font-size="12" lengthAdjust="spacing" textLength="131" x="726" y="148.6445">EXP-1  serialize models</text><line style="stroke:#181818;stroke-width:1.5;" x1="716" x2="726" y1="175.8281" y2="175.8281"/><text fill="#000000" font-family="sans-serif" font-size="12" lengthAdjust="spacing" textLength="173" x="726" y="180.7383">EXP-2  pass through unknowns</text><line style="stroke:#181818;stroke-width:1.5;" x1="716" x2="716" y1="120.1875" y2="175.8281"/><line style="stroke:#181818;stroke-width:1.5;" x1="48" x2="716" y1="65.0938" y2="65.0938"/><rect fill="#F1F1F1" height="35.0938" style="stroke:#181818;stroke-width:1.5;" width="102" x="331" y="10"/><text fill="#000000" font-family="sans-serif" font-size="12" lengthAdjust="spacing" textLength="82" x="341" y="32.457">nastran-parser</text><line style="stroke:#181818;stroke-width:1.5;" x1="382" x2="382" y1="45.0938" y2="65.0938"/><!--SRC=[LL71RXen4BtxA-QOK1711dhOKngWLIXGbDAejyYx7XOBxtWrjad8rsTSXMvxz3pFUs_UkmjHStof0kmJrT5wqkwvOjH7urz83O1qYAnfs6aEo6em04iHkMECVvw3PtZOx8PZ01q2jfL3YFWQmLd2qEC5W96DEiBUSwjZZzo2C8eBYbP7XDORT04-mKaxQsII9RMuEhzTzBviLbclzeaYr9fDwESVEjoAF8Zl1ly1HKfyooK88RMjvdCcPwJKLiWN-iVD_SSvjg7_E38Y0gdBlk1X3dkBplHOvlTTSXbrtXzJb_dnjVFyDwp5xsrcbooj7FXsERW7HQ0JROW7zgavGA8ZIHL1tI4PAKgfhPEmVgrNS48EqXYCRufHCRcvlTeT4dp52iPJA4RbP5IEfZ1Rx233r-hgstPrAY3un3M2iLAihLBk_5ejzKd3emHgMopXHuUqd7-_36119ykUMgIeba_h_iFdoV3UHlY9B5xWQQtckDV9HTcelR7Kb33hniMqK2l9CUb6o0sgMQwEpoNC5-y0]--></g></svg></div>
<<<

[REQUIREMENT]
MID: a8b9c0d1e2f3a4b5c6d7e8f9a0b1c2d3
UID: NFR-1
TITLE: Processing performance
STATUS: DRAFT
STATEMENT: >>>
The system shall process BDF streams with minimal CPU overhead, enabling handling of
large models without significant impact on overall execution time.
<<<
ACCEPTANCE_CRITERIA: >>>
A 100 MB BDF file is fully processed (read, interpreted, summary returned) in under
10 seconds on a modern laptop running Python 3.12. CPU utilisation during processing
does not exceed single-core capacity on the hot path.
<<<
MEANS_OF_COMPLIANCE: >>>
Use Python generator pipelines to eliminate intermediate allocations. Profile critical
parsing paths and apply targeted optimisations such as compiled regex patterns and
struct-based unpacking for fixed-width fields.
<<<

[REQUIREMENT]
MID: b9c0d1e2f3a4b5c6d7e8f9a0b1c2d3e4
UID: NFR-2
TITLE: Memory efficiency
STATUS: DRAFT
STATEMENT: >>>
The system shall maintain a minimal memory footprint during stream processing,
avoiding accumulation of data beyond what is required for the current processing step.
<<<
ACCEPTANCE_CRITERIA: >>>
Peak memory usage measured by a memory profiler while processing a 1 GB BDF file does
not exceed a configurable budget (default 128 MB). Memory usage does not grow
proportionally with file size.
<<<
MEANS_OF_COMPLIANCE: >>>
Implement the pipeline as a generator chain so no stage holds references to previously
yielded cards. Use __slots__ on card classes to minimise per-object overhead. Release
references to completed cards immediately after they are forwarded downstream.
<<<

[REQUIREMENT]
MID: c0d1e2f3a4b5c6d7e8f9a0b1c2d3e4f5
UID: NFR-3
TITLE: Adaptive memory consumption
STATUS: DRAFT
STATEMENT: >>>
The system shall dynamically adjust its memory consumption in response to the rate
and volume of incoming data, preventing unbounded memory growth.
<<<
ACCEPTANCE_CRITERIA: >>>
When a downstream stage processes cards more slowly than the source produces them,
the source reads no further ahead than one configured buffer. Memory usage under
back-pressure remains bounded and does not increase over time.
<<<
MEANS_OF_COMPLIANCE: >>>
Leverage Python generator back-pressure: the source only advances to the next chunk
when the downstream consumer calls next() on the iterator. No intermediate buffer or
queue is inserted between stages unless explicitly configured.
<<<

[REQUIREMENT]
MID: d1e2f3a4b5c6d7e8f9a0b1c2d3e4f5a6
UID: NFR-4
TITLE: Modularity
STATUS: DRAFT
STATEMENT: >>>
The system shall support the addition of new processing pipeline stages without
requiring modification of existing stages or the core stream infrastructure.
<<<
ACCEPTANCE_CRITERIA: >>>
A new pipeline stage can be implemented, registered, and wired into a workflow by
adding a single class and a task descriptor entry, with no changes to existing stage
classes or the pipeline runner. Existing workflows continue to pass their tests.
<<<
MEANS_OF_COMPLIANCE: >>>
Define a PipelineStage abstract base class (or Protocol) with a standard
process(cards: Iterator[Card]) -> Iterator[Card] interface. The pipeline factory
assembles stages by composition based on the task descriptor, with no hard-coded
stage references in the runner.
<<<

[REQUIREMENT]
MID: e2f3a4b5c6d7e8f9a0b1c2d3e4f5a6b7
UID: NFR-5
TITLE: PyPI distribution
STATUS: DRAFT
STATEMENT: >>>
The system shall be published as a Python package on PyPI and be installable via
pip or uv without additional build steps.
<<<
ACCEPTANCE_CRITERIA: >>>
pip install nastran-parser succeeds on Python 3.12+ on Windows, macOS, and Linux
without requiring a compiler or any system-level dependencies. The installed package
is importable immediately after installation.
<<<
MEANS_OF_COMPLIANCE: >>>
Maintain a pure-Python implementation with no C extensions or compiled dependencies.
Use uv build to produce a wheel and sdist, and uv publish to upload to PyPI. Automate
publishing via CI on tagged releases.
<<<
