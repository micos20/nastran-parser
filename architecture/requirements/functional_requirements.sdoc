[DOCUMENT]
MID: c7decfcff3d6484685a36511f1a81f63
TITLE: Functional Requirements
PREFIX: FR-
OPTIONS:
  ENABLE_MID: True

[GRAMMAR]
IMPORT_FROM_FILE: @grammar

[TEXT]
STATEMENT: >>>
.. raw:: html

   <div style="overflow-x:auto;margin:1em 0"><svg xmlns="http://www.w3.org/2000/svg" xmlns:xlink="http://www.w3.org/1999/xlink" contentStyleType="text/css" height="228px" preserveAspectRatio="none" style="width:914px;height:228px;background:#FFFFFF;" version="1.1" viewBox="0 0 914 228" width="914px" zoomAndPan="magnify"><defs/><g><line style="stroke:#181818;stroke-width:1.5;" x1="48" x2="48" y1="65.0938" y2="85.0938"/><rect fill="#F1F1F1" height="35.0938" style="stroke:#181818;stroke-width:1.5;" width="76" x="10" y="85.0938"/><text fill="#000000" font-family="sans-serif" font-size="12" lengthAdjust="spacing" textLength="56" x="20" y="107.5508">interpreter</text><line style="stroke:#181818;stroke-width:1.5;" x1="48" x2="58" y1="143.7344" y2="143.7344"/><text fill="#000000" font-family="sans-serif" font-size="12" lengthAdjust="spacing" textLength="143" x="58" y="148.6445">INT-1  assemble text lines</text><line style="stroke:#181818;stroke-width:1.5;" x1="48" x2="58" y1="175.8281" y2="175.8281"/><text fill="#000000" font-family="sans-serif" font-size="12" lengthAdjust="spacing" textLength="107" x="58" y="180.7383">INT-2  detect format</text><line style="stroke:#181818;stroke-width:1.5;" x1="48" x2="58" y1="207.9219" y2="207.9219"/><text fill="#000000" font-family="sans-serif" font-size="12" lengthAdjust="spacing" textLength="193" x="58" y="212.832">INT-3  instantiate models + validate</text><line style="stroke:#181818;stroke-width:1.5;" x1="48" x2="48" y1="120.1875" y2="207.9219"/><line style="stroke:#181818;stroke-width:1.5;" x1="306.5" x2="306.5" y1="65.0938" y2="85.0938"/><rect fill="#F1F1F1" height="35.0938" style="stroke:#181818;stroke-width:1.5;" width="65" x="274" y="85.0938"/><text fill="#000000" font-family="sans-serif" font-size="12" lengthAdjust="spacing" textLength="45" x="284" y="107.5508">analyzer</text><line style="stroke:#181818;stroke-width:1.5;" x1="306.5" x2="316.5" y1="143.7344" y2="143.7344"/><text fill="#000000" font-family="sans-serif" font-size="12" lengthAdjust="spacing" textLength="104" x="316.5" y="148.6445">ANL-1  count cards</text><line style="stroke:#181818;stroke-width:1.5;" x1="306.5" x2="316.5" y1="175.8281" y2="175.8281"/><text fill="#000000" font-family="sans-serif" font-size="12" lengthAdjust="spacing" textLength="138" x="316.5" y="180.7383">ANL-2  determine ranges</text><line style="stroke:#181818;stroke-width:1.5;" x1="306.5" x2="316.5" y1="207.9219" y2="207.9219"/><text fill="#000000" font-family="sans-serif" font-size="12" lengthAdjust="spacing" textLength="138" x="316.5" y="212.832">ANL-3  prepare summary</text><line style="stroke:#181818;stroke-width:1.5;" x1="306.5" x2="306.5" y1="120.1875" y2="207.9219"/><line style="stroke:#181818;stroke-width:1.5;" x1="520" x2="520" y1="65.0938" y2="85.0938"/><rect fill="#F1F1F1" height="35.0938" style="stroke:#181818;stroke-width:1.5;" width="85" x="477.5" y="85.0938"/><text fill="#000000" font-family="sans-serif" font-size="12" lengthAdjust="spacing" textLength="65" x="487.5" y="107.5508">renumberer</text><line style="stroke:#181818;stroke-width:1.5;" x1="520" x2="530" y1="143.7344" y2="143.7344"/><text fill="#000000" font-family="sans-serif" font-size="12" lengthAdjust="spacing" textLength="123" x="530" y="148.6445">RNB-1  assign ranges</text><line style="stroke:#181818;stroke-width:1.5;" x1="520" x2="530" y1="175.8281" y2="175.8281"/><text fill="#000000" font-family="sans-serif" font-size="12" lengthAdjust="spacing" textLength="122" x="530" y="180.7383">RNB-2  update ID field</text><line style="stroke:#181818;stroke-width:1.5;" x1="520" x2="530" y1="207.9219" y2="207.9219"/><text fill="#000000" font-family="sans-serif" font-size="12" lengthAdjust="spacing" textLength="131" x="530" y="212.832">RNB-3  populate lookup</text><line style="stroke:#181818;stroke-width:1.5;" x1="520" x2="520" y1="120.1875" y2="207.9219"/><line style="stroke:#181818;stroke-width:1.5;" x1="716" x2="716" y1="65.0938" y2="85.0938"/><rect fill="#F1F1F1" height="35.0938" style="stroke:#181818;stroke-width:1.5;" width="64" x="684" y="85.0938"/><text fill="#000000" font-family="sans-serif" font-size="12" lengthAdjust="spacing" textLength="44" x="694" y="107.5508">exporter</text><line style="stroke:#181818;stroke-width:1.5;" x1="716" x2="726" y1="143.7344" y2="143.7344"/><text fill="#000000" font-family="sans-serif" font-size="12" lengthAdjust="spacing" textLength="131" x="726" y="148.6445">EXP-1  serialize models</text><line style="stroke:#181818;stroke-width:1.5;" x1="716" x2="726" y1="175.8281" y2="175.8281"/><text fill="#000000" font-family="sans-serif" font-size="12" lengthAdjust="spacing" textLength="173" x="726" y="180.7383">EXP-2  pass through unknowns</text><line style="stroke:#181818;stroke-width:1.5;" x1="716" x2="716" y1="120.1875" y2="175.8281"/><line style="stroke:#181818;stroke-width:1.5;" x1="48" x2="716" y1="65.0938" y2="65.0938"/><rect fill="#F1F1F1" height="35.0938" style="stroke:#181818;stroke-width:1.5;" width="102" x="331" y="10"/><text fill="#000000" font-family="sans-serif" font-size="12" lengthAdjust="spacing" textLength="82" x="341" y="32.457">nastran-parser</text><line style="stroke:#181818;stroke-width:1.5;" x1="382" x2="382" y1="45.0938" y2="65.0938"/><!--SRC=[LL71RXen4BtxA-QOK1711dhOKngWLIXGbDAejyYx7XOBxtWrjad8rsTSXMvxz3pFUs_UkmjHStof0kmJrT5wqkwvOjH7urz83O1qYAnfs6aEo6em04iHkMECVvw3PtZOx8PZ01q2jfL3YFWQmLd2qEC5W96DEiBUSwjZZzo2C8eBYbP7XDORT04-mKaxQsII9RMuEhzTzBviLbclzeaYr9fDwESVEjoAF8Zl1ly1HKfyooK88RMjvdCcPwJKLiWN-iVD_SSvjg7_E38Y0gdBlk1X3dkBplHOvlTTSXbrtXzJb_dnjVFyDwp5xsrcbooj7FXsERW7HQ0JROW7zgavGA8ZIHL1tI4PAKgfhPEmVgrNS48EqXYCRufHCRcvlTeT4dp52iPJA4RbP5IEfZ1Rx233r-hgstPrAY3un3M2iLAihLBk_5ejzKd3emHgMopXHuUqd7-_36119ykUMgIeba_h_iFdoV3UHlY9B5xWQQtckDV9HTcelR7Kb33hniMqK2l9CUb6o0sgMQwEpoNC5-y0]--></g></svg></div>
<<<

[REQUIREMENT]
MID: a1b2c3d4e5f6a7b8c9d0e1f2a3b4c5d6
UID: FR-1
TITLE: Read BDF from filesystem
STATUS: DRAFT
STATEMENT: >>>
The system shall read BDF input files from the local filesystem as a data stream.
<<<
ACCEPTANCE_CRITERIA: >>>
A BDF file on the local filesystem can be opened and its content streamed card by card
through the pipeline. The file is not fully loaded into memory at any point.
<<<
MEANS_OF_COMPLIANCE: >>>
Implement a FileSystemSource class that opens files using Python buffered I/O and yields
card-aligned chunks on demand via the iterator protocol.
<<<
FUNCTIONS: INT-1

[REQUIREMENT]
MID: b2c3d4e5f6a7b8c9d0e1f2a3b4c5d6e7
UID: FR-2
TITLE: Read BDF from network
STATUS: DRAFT
STATEMENT: >>>
The system shall read BDF input from a URL or REST endpoint as a data stream.
<<<
ACCEPTANCE_CRITERIA: >>>
A BDF file served over HTTP can be streamed through the pipeline without downloading
the complete file first. The source yields data as the network delivers it.
<<<
MEANS_OF_COMPLIANCE: >>>
Implement a NetworkSource class using an HTTP client with streaming enabled (e.g.
httpx with stream=True), yielding card-aligned chunks as they arrive.
<<<
FUNCTIONS: INT-1

[REQUIREMENT]
MID: c3d4e5f6a7b8c9d0e1f2a3b4c5d6e7f8
UID: FR-3
TITLE: Interpret NASTRAN card stream
STATUS: DRAFT
STATEMENT: >>>
The system shall parse and validate NASTRAN card content from a chunked data stream,
identifying card type, extracting field values, and validating field types.
<<<
ACCEPTANCE_CRITERIA: >>>
Given a stream of BDF content, the interpreter correctly identifies all card types,
extracts every field value, and rejects fields whose values do not match the declared
type (Integer, Real, or Character). Continuation lines are assembled into a single card.
<<<
MEANS_OF_COMPLIANCE: >>>
Implement a card interpreter that detects small-field, large-field, and free-field
formats per card. Use card definitions to extract and type-validate each field.
Accumulate continuation lines before dispatching the completed card downstream.
<<<
FUNCTIONS: INT-1, INT-2, INT-3

[REQUIREMENT]
MID: d4e5f6a7b8c9d0e1f2a3b4c5d6e7f8a9
UID: FR-4
TITLE: Modify card field values
STATUS: DRAFT
STATEMENT: >>>
The system shall allow modification of individual field values on a parsed NASTRAN card.
<<<
ACCEPTANCE_CRITERIA: >>>
A field value on a parsed card can be updated programmatically. The change is reflected
when the card is subsequently serialized. Assignment of a value with an incompatible
type raises a descriptive error.
<<<
MEANS_OF_COMPLIANCE: >>>
Expose mutable field attributes on each typed card class. Validate the new value against
the field type constraint on assignment and raise a TypeError with the field name and
expected type if the constraint is violated.
<<<
FUNCTIONS: INT-3

[REQUIREMENT]
MID: e5f6a7b8c9d0e1f2a3b4c5d6e7f8a9b0
UID: FR-5
TITLE: Write BDF to filesystem
STATUS: DRAFT
STATEMENT: >>>
The system shall serialize and write BDF output to the local filesystem.
<<<
ACCEPTANCE_CRITERIA: >>>
A sequence of card objects can be serialized to a file. The resulting BDF file is
parseable as valid input by the same parser without errors or data loss.
<<<
MEANS_OF_COMPLIANCE: >>>
Implement a FileSystemSink class that serializes each card back to its original format
(small-field, large-field, or free-field) and writes to a file using buffered I/O,
flushing on completion.
<<<
FUNCTIONS: EXP-1, EXP-2

[REQUIREMENT]
MID: f6a7b8c9d0e1f2a3b4c5d6e7f8a9b0c1
UID: FR-6
TITLE: Write BDF to network
STATUS: DRAFT
STATEMENT: >>>
The system shall serialize and stream BDF output to a URL or REST endpoint.
<<<
ACCEPTANCE_CRITERIA: >>>
A sequence of card objects can be serialized and sent to an HTTP endpoint without
buffering the complete output in memory. The endpoint receives valid BDF content.
<<<
MEANS_OF_COMPLIANCE: >>>
Implement a NetworkSink class that streams serialized card data to a URL via HTTP using
chunked transfer encoding, writing each card as it is received from the upstream stage.
<<<
FUNCTIONS: EXP-1, EXP-2

[REQUIREMENT]
MID: a7b8c9d0e1f2a3b4c5d6e7f8a9b0c1d2
UID: FR-7
TITLE: Track file content summary
STATUS: DRAFT
STATEMENT: >>>
The system shall record the card type and card ID for every card encountered during
stream processing and return a file summary upon stream completion.
<<<
ACCEPTANCE_CRITERIA: >>>
After processing a BDF stream, the returned FileSummary lists every distinct card type
encountered, the total count per type, and the ID of each individual card. The summary
is correct even when the stream is processed in a single pass without re-reading.
<<<
MEANS_OF_COMPLIANCE: >>>
Accumulate a FileSummary data structure during stream processing. Each interpreted card
contributes its type and ID to the summary before being forwarded to the next stage.
Return the completed summary when the stream is exhausted.
<<<
FUNCTIONS: ANL-1, ANL-2, ANL-3

[REQUIREMENT]
MID: b8c9d0e1f2a3b4c5d6e7f8a9b0c1d2e3
UID: FR-8
TITLE: Chunked stream processing
STATUS: DRAFT
STATEMENT: >>>
The system shall process BDF input in chunks without loading the complete file into memory.
The chunk boundary shall align to card boundaries (not byte offsets).
<<<
ACCEPTANCE_CRITERIA: >>>
Processing a BDF file larger than available RAM completes successfully. Peak memory usage
measured by a memory profiler does not grow proportionally with file size.
<<<
MEANS_OF_COMPLIANCE: >>>
Implement the processing pipeline as a Python generator chain. Each stage yields one
card at a time and holds no references to previously yielded cards. Chunk boundaries
are determined by detecting the end of a complete card (including continuation lines).
<<<
FUNCTIONS: INT-1

[REQUIREMENT]
MID: c9d0e1f2a3b4c5d6e7f8a9b0c1d2e3f4
UID: FR-9
TITLE: Task-based pipeline configuration
STATUS: DRAFT
STATEMENT: >>>
The system shall configure the processing pipeline via a task type supplied by the caller
at the start of a stream (e.g. read-only, renumber).
<<<
ACCEPTANCE_CRITERIA: >>>
The same pipeline infrastructure executes a read-only task and a renumber task when
supplied with the respective task descriptor, without any code change between runs.
Different task types produce the correct sequence of pipeline stages.
<<<
MEANS_OF_COMPLIANCE: >>>
Implement a pipeline factory that assembles the ordered list of stages based on the
supplied task descriptor before the stream is opened. Each task type maps to a fixed
stage composition defined in the factory.
<<<

[REQUIREMENT]
MID: d0e1f2a3b4c5d6e7f8a9b0c1d2e3f4a5
UID: FR-10
TITLE: Renumber card IDs
STATUS: DRAFT
STATEMENT: >>>
The system shall renumber card IDs according to a caller-supplied ruleset during stream
processing, generating new IDs from defined number ranges.
<<<
ACCEPTANCE_CRITERIA: >>>
Given a renumbering ruleset, all card IDs in the output BDF fall within the specified
target ranges. IDs that cross-reference other cards are updated consistently so the
output BDF remains internally coherent.
<<<
MEANS_OF_COMPLIANCE: >>>
Implement a RenumberStage that loads the ruleset, maintains a counter per target range,
and maps each original ID to the next available ID in the corresponding range. Apply
the mapping to all ID fields of each card before forwarding it downstream.
<<<
FUNCTIONS: RNB-1, RNB-2

[REQUIREMENT]
MID: e1f2a3b4c5d6e7f8a9b0c1d2e3f4a5b6
UID: FR-11
TITLE: ID mapping table
STATUS: DRAFT
STATEMENT: >>>
The system shall maintain a lookup table mapping old card IDs to new card IDs during
renumbering, returned as part of the file summary on stream completion.
<<<
ACCEPTANCE_CRITERIA: >>>
The FileSummary returned after a renumber operation contains a complete mapping of every
original card ID to its assigned new ID. The mapping covers all card types that carry IDs.
<<<
MEANS_OF_COMPLIANCE: >>>
Maintain a dictionary in RenumberStage keyed by original ID and updated as each card
is processed. Include the completed mapping in the FileSummary returned on stream
completion.
<<<
FUNCTIONS: RNB-3
